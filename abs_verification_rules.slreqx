# abs_verification_rules

## REQ-01: ABS Stopping Distance Reduction (Functional)
The Anti-Lock Braking System (ABS) controller must reduce the total vehicle stopping distance by a minimum of 3% compared to the same vehicle braking with ABS disabled. This performance standard must be met across all simulated road conditions, including Dry (mu=0.80), Wet (mu=0.50), and Ice (mu=0.15).
- Rationale: The primary safety objective of an ABS is to stop the vehicle in a shorter distance than a locked-wheel skid. The 3% margin accounts for varying tire radii, vehicle masses, and initial velocities.

## REQ-02: Optimal Wheel Slip Regulation (Functional)
The controller must actively regulate brake pressure to maintain the longitudinal wheel slip ratio near the target slip value for the given road condition. During active braking, the maximum wheel slip must not exceed the target slip ratio by a margin greater than 0.15.
- Rationale: Exceeding the optimal slip ratio leads to wheel lock-up, loss of steering control, and reduced braking force. Keeping it within a strict tolerance ensures maximum tire-to-road friction.

## REQ-03: Target Processor Numerical Equivalence (Functional)
The compiled C-code executing on the Arm Cortex-M7 Fast Model Emulator (Processor-in-the-Loop) must produce control outputs and stopping distances numerically identical to those generated by the host-based Simulink simulation (Model-in-the-Loop). The absolute error between MIL and PIL stopping distances must be zero (within standard floating-point tolerance).
- Rationale: Proves that the Embedded Coder toolchain generated mathematically accurate C-code without causing data type truncations, overflows, or solver mismatches on the target architecture.

## REQ-04: Arm Cortex-M7 CPU Utilization (Functional)
The ABS controller task must execute on the Arm Cortex-M7 target hardware without missing real-time scheduling deadlines. For a controller sample time of 0.01 seconds (10 ms), the maximum execution time of the generated C-code must not exceed a CPU utilization threshold of 70%.
- Rationale: In a real automotive Electronic Control Unit (ECU), the processor must handle multiple tasks (engine timing, airbags, etc.). The ABS logic must run fast enough to leave headroom for the rest of the operating system.

## REQ-05: The PID controller output shall remain within the physically valid brake pressure range at all times. (Functional)
The brake pressure command output of the ABS controller shall remain within the closed interval [0, PBmax] throughout the entire simulation. Negative brake pressure commands and commands exceeding PBmax are not physically realizable and shall never occur. This shall be verified across all 35 test cases under both MIL and PIL.
- Rationale: Unbounded controller output indicates PID windup, instability, or saturation handling failure. In a real braking system, an out-of-range command would either be silently clamped by the actuator — masking a controller fault — or cause actuator damage. Explicit verification ensures the PID is correctly tuned and its output saturation logic is functioning.

## REQ-06: The ABS controller shall meet slip and stopping distance requirements across all defined road surface types. (Functional)
The system shall satisfy REQ-01 and REQ-02 independently for each of the following surface categories: Dry (μ ≥ 0.70), Wet (0.40 ≤ μ < 0.70), Ice (μ < 0.20), and Mixed/Transitional surfaces (Snow, Gravel, Wet Leaves). At least 80% of test cases within each surface category shall pass all applicable criteria.
- Rationale: Road surface friction varies widely in real-world operation. A controller that works only on dry roads provides inadequate safety. Explicit per-surface pass rate requirements ensure the PID tuning and slip targets are robust across the full operational envelope rather than optimized for a single condition.

## REQ-07: The PID controller shall bring wheel slip within the target band within 0.5 seconds of brake application. (Functional)
Following the onset of braking (t = 0s), the wheel slip ratio shall enter and remain within the band [slip_target − 0.05, slip_target + 0.10] within 0.5 seconds for dry and wet surfaces, and within 0.8 seconds for ice surfaces. Oscillatory behavior where slip repeatedly exits and re-enters the band after the settling time constitutes a failure of this requirement.
- Rationale: A PID controller that is too slow to respond allows extended wheel lockup during the critical early braking phase, significantly increasing stopping distance. A controller that overshoots excessively wastes braking force and risks instability. Settling time requirements define the minimum acceptable transient performance of the PID tuning.

## REQ-08: When ABS is disabled, the controller shall apply no brake modulation and shall not influence brake pressure. (Functional)
When the enable signal ctrl = 0, the ABS controller output shall be equivalent to full constant brake pressure application with no modulation. The slip ratio shall be free to evolve without controller intervention. Stopping distance with ctrl = 0 shall be greater than or equal to stopping distance with ctrl = 1 across all test cases, confirming the enable/disable switching path is functionally correct.
- Rationale: The ABS enable/disable path is a safety-critical function. If the controller continues to modulate brakes when commanded off, it constitutes an unintended actuation — a safety hazard. This requirement verifies the ctrl signal correctly gates the controller and that the ABS-OFF baseline used throughout the test suite is a valid uncontrolled reference.

## REQ-09: The vehicle shall decelerate to rest within the simulation time window for all test cases. (Functional)
The vehicle speed Vs shall fall below 2 rad/s before the simulation stop time tEnd for all 35 test cases under ABS-ON conditions. Cases where the vehicle has not stopped by tEnd indicate either insufficient brake force, an unreachable slip target for the given road condition, or an incorrectly set simulation duration.
- Rationale: A braking controller that fails to bring the vehicle to rest is functionally incomplete. This requirement catches cases where PID tuning is too conservative, the brake pressure limit is too low for the road condition, or the simulation window is too short — all of which would invalidate test results by measuring an incomplete braking event.

## REQ-10: The ABS controller shall prevent complete wheel lockup under all braking conditions. (Functional)
During ABS-active braking, the wheel slip ratio shall never exceed 0.95 at any point during the simulation (from t = 0s to tEnd). A slip ratio of 1.0 represents complete wheel lockup. The 0.95 threshold provides a 5% margin to account for measurement and signal processing latency. This shall be verified under all 35 test cases and all road surface types.
- Rationale: Complete wheel lockup eliminates lateral tire force, causing loss of vehicle steering control — the primary safety failure mode that ABS exists to prevent. While REQ-02 ensures average slip stays near the optimum, REQ-10 is a hard safety floor that ensures no instantaneous lockup event occurs even during transients, surface transitions, or controller lag.
